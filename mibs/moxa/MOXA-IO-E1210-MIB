-- *****************************************************************
-- Moxa Active Ethernet I/O Server MIB
--
-- 01-03-2013
--
-- Copyright (c) 2013 by Moxa Automation Co., Ltd.
-- All rights reserved.
-- *****************************************************************

MOXA-IO-E1210-MIB DEFINITIONS ::= BEGIN
    IMPORTS
        enterprises, Unsigned32, Integer32, MODULE-IDENTITY, OBJECT-TYPE, NOTIFICATION-TYPE FROM SNMPv2-SMI;
-- 1.3.6.1.4.1.8691.10.1210
    e1210   MODULE-IDENTITY
    LAST-UPDATED "201607281600Z"
    ORGANIZATION "Moxa Automation,Inc."
    CONTACT-INFO
            "Postal: Moxa Automation,Inc.
             Fl.4, No.135,Lane 235,Pao-Chiao Rd.
             Shing Tien City,Taipei,Taiwan,R.O.C
             Tel: +866-2-89191230 "
    DESCRIPTION
            "The MIB module for Moxa ioLogik Remote Ethernet I/O specific information." 

	REVISION "201607281600Z"      
	DESCRIPTION
            "add item of counter_overflow_clear"
					
			
	REVISION "201603301000Z"      
	DESCRIPTION
            "Support reset to init and clear overflow in di-counter mode"
				
	REVISION "201601140900Z"      
	DESCRIPTION
            "remove di type entry"
			
	REVISION "201601041300Z"      
	DESCRIPTION
            "Validate level 3 of simple web"
		
	REVISION "201512041600Z"
	DESCRIPTION
            "First version of this MIB."
    REVISION "201302211400Z"    
    DESCRIPTION
            "The Trap Support SNMPv2"    
            
            
           ::= { ioLogik 1210 }    -- 1.3.6.1.4.1.8691.10.1210

-- 1.3.6.1.4.1.8691
    moxa OBJECT IDENTIFIER ::= { enterprises 8691 }

-- 1.3.6.1.4.1.8691.10
    ioLogik OBJECT IDENTIFIER ::= { moxa 10 }

-- 1.3.6.1.4.1.8691.10.1210.1
    totalChannelNumber OBJECT-TYPE
        SYNTAX Integer32 (1..16)
        MAX-ACCESS read-only
        STATUS current
        DESCRIPTION
            "Total I/O channels."
        ::= { e1210 1 }

-- 1.3.6.1.4.1.8691.10.1210.2
    serverModel OBJECT-TYPE
        SYNTAX OCTET STRING
        MAX-ACCESS read-only
        STATUS current
        DESCRIPTION
            "The I/O server model."
        ::= { e1210 2 }

-- 1.3.6.1.4.1.8691.10.1210.3
    systemTime OBJECT-TYPE
        SYNTAX Integer32
        MAX-ACCESS read-only
        STATUS current
        DESCRIPTION
            "I/O server up time (in seconds)."
        ::= { e1210 3 }

-- 1.3.6.1.4.1.8691.10.1210.4
    firmwareVersion OBJECT-TYPE
        SYNTAX OCTET STRING
        MAX-ACCESS read-only
        STATUS current
        DESCRIPTION
            "The firmware version."
        ::= { e1210 4 }


----------------------------------------------------------------
-- I/O
-- 1.3.6.1.4.1.8691.10.1210.10          
    e1210monitor OBJECT IDENTIFIER ::= { e1210 10 }
----------------------------------------------------------------
-- DI channel
diTable OBJECT-TYPE
        SYNTAX          SEQUENCE OF DIEntry
        MAX-ACCESS      not-accessible
        STATUS          current
        DESCRIPTION     
            "The DI channel monitor table"
        ::= { e1210monitor 1 }

diEntry OBJECT-TYPE
        SYNTAX          DIEntry
        MAX-ACCESS      not-accessible
        STATUS          current
        DESCRIPTION     
            "The DI channel monitor item"
        INDEX { diIndex }
        ::= { diTable 1 }

DIEntry ::= SEQUENCE {
                diIndex     Integer32,
                diMode      Integer32,
                diStatus    Integer32,
                diFilter    Integer32,
                diTrigger   Integer32,
                diCntStart  Integer32,
				diCounterReset Integer32,
				diCounterOverflowFlag Integer32,
				diCounterOverflowFlagClear Integer32
                 }

diIndex OBJECT-TYPE
        SYNTAX          Integer32  (0..15)
        MAX-ACCESS      read-only
        STATUS          current
        DESCRIPTION     
            "DI - index"
        ::= { diEntry 1 }           
        
diMode OBJECT-TYPE
        SYNTAX          Integer32  (0..1)
        MAX-ACCESS      read-write
        STATUS          current
        DESCRIPTION     "DI - mode (0: DI, 1: Counter mode)"
        ::= { diEntry 3 }
        
diStatus OBJECT-TYPE
        SYNTAX          Integer32 (0..2147483647)
        MAX-ACCESS      read-only
        STATUS          current
        DESCRIPTION     "DI - DI mode status (0: OFF, 1: ON) or Counter mode value"
        ::= { diEntry 4 }
        
diFilter OBJECT-TYPE
        SYNTAX          Integer32  (1..65535)
        MAX-ACCESS      read-write
        STATUS          current
        DESCRIPTION     "DI - filter setting (unit: 1 ms)"
        ::= { diEntry 5 }

diTrigger OBJECT-TYPE
        SYNTAX          Integer32  (0..2)
        MAX-ACCESS      read-write
        STATUS          current
        DESCRIPTION     "DI - Counter mode - event (0: Rising Edge, 1: Falling Edge, 2: Both)"
        ::= { diEntry 6 }

diCntStart OBJECT-TYPE
        SYNTAX          Integer32 (0..1)
        MAX-ACCESS      read-write
        STATUS          current
        DESCRIPTION     "DI - Counter mode - status (0: STOP, 1: START)"
        ::= { diEntry 7 }

diCounterReset OBJECT-TYPE
        SYNTAX          Integer32 (0..1)
        MAX-ACCESS      read-write
        STATUS          current
        DESCRIPTION     "DI - Counter mode - reset to initial value (1: RESET)"
        ::= { diEntry 8 }		
	
diCounterOverflowFlag OBJECT-TYPE
        SYNTAX          Integer32 (0..1)
        MAX-ACCESS      read-only
        STATUS          current
        DESCRIPTION     "DI - Counter mode - overflow flag (0: Normal, 1: Overflow)"
        ::= { diEntry 9 }		

diCounterOverflowFlagClear OBJECT-TYPE
        SYNTAX          Integer32 (0..1)
        MAX-ACCESS      read-write
        STATUS          current
        DESCRIPTION     "DI - Counter mode - clear overflow flag (1:CLEAR)"
        ::= { diEntry 10 }			
----------------------------------------------------------------
-- DI TRAP
-- 1.3.6.1.4.1.8691.10.1210.20
    diTrap OBJECT IDENTIFIER ::= { e1210 20 }

----------------------------------------------------------------
diTrap0 NOTIFICATION-TYPE
		STATUS current
    	DESCRIPTION     "DI-00 - DI mode - status (0: OFF, 1: ON)"
        ::= { diTrap 1 }

diTrap1 NOTIFICATION-TYPE
		STATUS current
    	DESCRIPTION     "DI-01 - DI mode - status (0: OFF, 1: ON)"
        ::= { diTrap 2 }  
        
diTrap2 NOTIFICATION-TYPE
		STATUS current
    	DESCRIPTION     "DI-02 - DI mode - status (0: OFF, 1: ON)"
        ::= { diTrap 3 }

diTrap3 NOTIFICATION-TYPE
		STATUS current
    	DESCRIPTION     "DI-03 - DI mode - status (0: OFF, 1: ON)"
        ::= { diTrap 4 }  
        
diTrap4 NOTIFICATION-TYPE
		STATUS current
    	DESCRIPTION     "DI-04 - DI mode - status (0: OFF, 1: ON)"
        ::= { diTrap 5 }

diTrap5 NOTIFICATION-TYPE
		STATUS current
    	DESCRIPTION     "DI-05 - DI mode - status (0: OFF, 1: ON)"
        ::= { diTrap 6 }
        
diTrap6 NOTIFICATION-TYPE
		STATUS current
    	DESCRIPTION     "DI-06 - DI mode - status (0: OFF, 1: ON)"
        ::= { diTrap 7 }

diTrap7 NOTIFICATION-TYPE
		STATUS current
    	DESCRIPTION     "DI-07 - DI mode - status (0: OFF, 1: ON)"
        ::= { diTrap 8 }

diTrap8 NOTIFICATION-TYPE
		STATUS current
    	DESCRIPTION     "DI-08 - DI mode - status (0: OFF, 1: ON)"
        ::= { diTrap 9 }

diTrap9 NOTIFICATION-TYPE
		STATUS current
    	DESCRIPTION     "DI-09 - DI mode - status (0: OFF, 1: ON)"
        ::= { diTrap 10 }  
        
diTrap10 NOTIFICATION-TYPE
		STATUS current
    	DESCRIPTION     "DI-10 - DI mode - status (0: OFF, 1: ON)"
        ::= { diTrap 11 } 
        
diTrap11 NOTIFICATION-TYPE
		STATUS current
    	DESCRIPTION     "DI-11 - DI mode - status (0: OFF, 1: ON)"
        ::= { diTrap 12 }

diTrap12 NOTIFICATION-TYPE
		STATUS current
    	DESCRIPTION     "DI-12 - DI mode - status (0: OFF, 1: ON)"
        ::= { diTrap 13 }

diTrap13 NOTIFICATION-TYPE
		STATUS current
    	DESCRIPTION     "DI-13 - DI mode - status (0: OFF, 1: ON)"
        ::= { diTrap 14 }

diTrap14 NOTIFICATION-TYPE
		STATUS current
    	DESCRIPTION     "DI-14 - DI mode - status (0: OFF, 1: ON)"
        ::= { diTrap 15 }  

diTrap15 NOTIFICATION-TYPE
		STATUS current
    	DESCRIPTION     "DI-15 - DI mode - status (0: OFF, 1: ON)"
        ::= { diTrap 16 }
 ----------------------------------------------------------------
-- Message TRAP
-- 1.3.6.1.4.1.8691.10.1210.30
	messageTrap OBJECT IDENTIFIER ::= { e1210 30 }

---------------------------------------------------------------- 
activeMessageTrap NOTIFICATION-TYPE
		STATUS current
		DESCRIPTION 	"The SNMP trap with active message"
        ::= { messageTrap 1 }



END
